Context-heater DEFINITIONS ::=
BEGIN
   IMPORTS
      T-Int32 FROM TASTE-BasicTypes;

--  Group all context parameters of this function in a record
Context-heater ::= SEQUENCE {
   gpio-pin T-Int32

}

--  Declare a constant with the values set by the user in the interface view
heater-ctxt Context-heater ::= {
   gpio-pin 12

}
END
