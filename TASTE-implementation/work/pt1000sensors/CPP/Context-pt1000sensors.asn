Context-pt1000sensors DEFINITIONS ::=
BEGIN
   IMPORTS
      T-Int32 FROM TASTE-BasicTypes
      PT1000s-Channels FROM TASEC-LAB-B2SPACE-DATAVIEW;

--  Group all context parameters of this function in a record
Context-pt1000sensors ::= SEQUENCE {
   vcc-ch T-Int32,
   channels PT1000s-Channels

}

--  Declare a constant with the values set by the user in the interface view
pt1000sensors-ctxt Context-pt1000sensors ::= {
   vcc-ch 7,
   channels {1, 3, 6, 5, 2, 4, 0}

}
END
