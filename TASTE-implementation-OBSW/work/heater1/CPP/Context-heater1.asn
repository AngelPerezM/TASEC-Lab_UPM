Context-heater1 DEFINITIONS ::=
BEGIN
   IMPORTS
      T-Int32 FROM TASTE-BasicTypes;

--  Group all context parameters of this function in a record
Context-heater1 ::= SEQUENCE {
   gpio-pin T-Int32

}

--  Declare a constant with the values set by the user in the interface view
heater1-ctxt Context-heater1 ::= {
   gpio-pin 12

}
END
