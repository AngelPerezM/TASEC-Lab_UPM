Heattransferlab-Datamodel DEFINITIONS ::=
BEGIN
IMPORTS
   T-Int16, T-UInt16, T-UInt64, T-Float, T-Double, File-Name, Content-Validity, SPI-ID, I2C-ID, GPS-PVT, MGT-Raw-Data, MGT-MilliGauss-Data, ACC-Raw-Data, ACC-MilliG-Data, GYRO-Raw-Data, GYRO-MilliDPS-Data, IMU-All-Data, TC74s-I2CBuses, TC74s-All-Data, PT1000s-Channels, PT1000s-Raw-Data, PT1000s-Celsius-Data, PT1000s-All-Data, PS-Calibration-Data, PS-Raw-Data, PS-Processed-Data, PS-All-Data, Heater-Data, Heater-On-Off, HTL-State, HTL-Config, OBSW-DP-Data, OBSW-DP-SingleData, OBSW-DP-Filter, TM, TC, HTL-GUI, Date-Time, ATT-GUI, PS-GUI, ENV-GUI FROM TASEC-LAB-B2SPACE-DATAVIEW
   T-Int32, T-UInt32, T-Int8, T-UInt8, T-Boolean, T-Null-Record FROM TASTE-BasicTypes;

Heattransferlab-States ::= ENUMERATED {a2, selectstate, error, f3, a1, f1, f2}

Heattransferlab-Context ::= SEQUENCE {
   state Heattransferlab-States,
   init-done BOOLEAN,
   ok T-Boolean,
   actual-state HTL-State,
   last-good-state HTL-State,
   temp-air T-Float,
   temp-plate T-Float,
   press T-Float,
   press-5km T-Float,
   press-10km T-Float,
   press-18km T-Float,
   power T-Float,
   htl-time T-Double,
   a1-duration-emergency T-Double,
   a1-duration-max T-Double,
   power-a2 T-Float,
   a2-duration-max T-Double,
   n T-Float,
   power-f1 T-Float,
   f1-duration T-UInt32,
   m T-Float,
   f2-duration T-UInt32
}

OBSW-DP-SingleData-selection ::= ENUMERATED {gps-present(1), imu-present(2), tc74s-present(3), pt1000s-present(4), ps1-present(5), ps2-present(6), heater1-present(7), heater2-present(8), anemometer-present(9)}
TC-heater-of-htl-selection ::= ENUMERATED {power-manual-present(1), max-min-present(2)}
END
